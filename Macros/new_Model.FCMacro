#!/usr/bin/env python
# coding: utf-8
# 
# Macro to create a new App::Part in a new file 
# for use with Assembly Without Solver
# The App::Part is called "Model" to avoid confusion

App.activeDocument().Tip = App.activeDocument().addObject('App::Part','Model')
App.activeDocument().getObject('Model').newObject('App::DocumentObjectGroup','Constraints')
App.activeDocument().getObject('Model').newObject('PartDesign::CoordinateSystem','LCS_0')
